submodule a-sub {
  yang-version 1.1;
  belongs-to main {
    prefix main;
  }

  revision 2026-03-20;

  feature a-sub-f;

  identity a-misc-id;

  container b-a {
    leaf value {
      type string;
    }
  }
}
