module submod-aug-main {
  yang-version 1.1;

  prefix sam;
  namespace "http://example.com/ns/submod-aug-main";

  include submod-aug-sub1;
  include submod-aug-sub2 {
    revision-date 2026-04-20;
  }
  include submod-aug-sub3;
}
