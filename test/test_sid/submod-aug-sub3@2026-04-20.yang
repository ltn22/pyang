submodule submod-aug-sub3 {
  yang-version 1.1;

  belongs-to submod-aug-main {
    prefix sam;
  }

  import submod-aug-dest {
    prefix sad;
  }

  revision 2026-04-20;
  revision 2026-04-15;

  augment "/sad:destination" {
    leaf new-node1-sub3 {
      type int16;
    }

    leaf new-node2-sub3 {
      type empty;
    }
  }
}
